[DOCUMENT]
TITLE: Software System Specification

[TEXT]
STATEMENT: >>>
The software system specification contains the customer’s requirements. It is generated by the system engineering processes related to software. It is the highest level description of the software and, together with the interface requirements document, provides the criteria that are used to validate and accept the software.

The information about traceability to high–level requirements can be in the software system specification or in the requirements traceability in the design justification file. In either case a cross–reference is done.

The software system specification can be produced as a standalone document or as part of a system–level specification document. It can be included, for example, in the technical specification introduced by ECSS‐E‐ST‐10‐06. If produced as a standalone document, the present DRD applies, else the DRD described in ECSS‐E‐ST‐10‐06 for the establishment of a functional and technical specification applies.

The software system specification is a major component of the requirements baseline and is the primary input for the system requirements review (SRR)

The requirements baseline towards the supplier includes, at each recursive level, the level of requirements detail necessary for an unambiguous implementation by the supplier. As on subsequent contractual levels, the design becomes more mature, and the implementation freedom is consequently more limited. This is reflected in the specification of requirements towards subcontractors who therefore, at lower contractual levels, receive more (design, implementation) constraining requirements.
<<<

[[SECTION]]
TITLE: Introduction

[TEXT]
STATEMENT: >>>
The SSS shall contain a description of the purpose, objective, content and the reason prompting its preparation.
<<<

[[/SECTION]]

[[SECTION]]
TITLE: Applicable and reference documents

[TEXT]
STATEMENT: >>>
a. The SRS shall list the applicable and reference documents to support the generation of the document.
<<<

[[/SECTION]]

[[SECTION]]
TITLE: Terms, definitions and abbreviated terms

[TEXT]
STATEMENT: >>>
a. The SSS shall include any additional terms, definition or abbreviated terms used.
<<<

[[/SECTION]]

[[SECTION]]
TITLE: General description

[[SECTION]]
TITLE: Product perspective

[TEXT]
STATEMENT: >>>
a. The SSS shall describe the product in perspective with other related systems.

b. If the product is to replace an existing system, the system shall be described and referenced.
<<<

[[/SECTION]]

[[SECTION]]
TITLE: General capabilities

[TEXT]
STATEMENT: >>>
a. The SSS shall describe the main capabilities to be supported by the software.

   NOTE: Reference to state and mode of the system can be made.
<<<

[[/SECTION]]

[[SECTION]]
TITLE: General constraints

[TEXT]
STATEMENT: >>>
a. The SSS shall describe any item that limits the supplier's options for designing and developing the software.
<<<

[[/SECTION]]

[[SECTION]]
TITLE: Operational environment

[TEXT]
STATEMENT: >>>
a. The SSS shall describe the software operational environment.

b. Context diagrams may support this narrative description to summarize external interfaces and system block diagrams to show how the activity fits within the larger system.

c. The nature of exchanges with external systems should be listed.

d. If a system specification defines a product that is a component of a parent system or project, then the SSS should list the activities that are supported by external systems.

e. References to the interface requirements documents that define the external interfaces with the other systems shall be provided

f. The computer infrastructure to be used shall be also described.
<<<

[[/SECTION]]

[[SECTION]]
TITLE: Assumptions and dependencies

[TEXT]
STATEMENT: >>>
a. The SSS shall list or make reference to the existing assumptions that the specific requirements are based on.

   NOTE 1: Risks analysis is used to identify assumptions that cannot prove to be valid.

   NOTE 2: A constraint requirement, for example, can specify an interface with a system which does not exist.

   NOTE 3: If the production of the system does not occur when expected, this system specification can change.
<<<

[[/SECTION]]

[[/SECTION]]

[[SECTION]]
TITLE: Specific requirements

[[SECTION]]
TITLE: General

[TEXT]
STATEMENT: >>>
NOTE: The following provisions apply to the system specific requirements listed in the SSS, as specified in <5.2> to <5.12> below:

a. Each requirement shall be uniquely identified.

b. When requirements are expressed as models, the supplier shall establish a way to assign identifiers within the model for sake of traceability.

c. Each requirement shall be associated to a validation method and a version, as per 5.2.4.1a. and ECSS‐Q‐ST‐80, 7.2.1.3.
<<<

[[/SECTION]]

[[SECTION]]
TITLE: Capabilities requirements (5.2.2.1a.)

[TEXT]
STATEMENT: >>>
a. The SSS shall list the requirements specifying the system behaviour and its associated performances.

b. Description of capability requirements shall be organized by capability type.

   NOTE: For example, requirements can be organized per controlled subsystem (e.g. AOCS, power, and thermal).

c. Capability requirements shall include the real‐time behaviour and constraints of the system (5.2.2.1f.)

d. The HMI capability requirements shall result from the human factor engineering process described in ECSS‐E‐ST‐10‐11 (5.2.2.3)

e. The SSS shall state the capabilities to be implemented by on‐board control procedures (OBCP) (5.2.4.6)
<<<

[[/SECTION]]

[[SECTION]]
TITLE: System interface requirements (5.2.4.3)

[TEXT]
STATEMENT: >>>
a. The SSS shall list (or refer to the IRD) any interface requirements imposed on the system.

b. The requirements of the following shall be either be listed in the SSS or referred to in the IRD:

   1. communication interfaces,
   2. hardware interfaces,
   3. software interfaces,
   4. HMI,
<<<

[[/SECTION]]

[[SECTION]]
TITLE: Adaptation and missionization requirements (5.2.4.4)

[TEXT]
STATEMENT: >>>
a. The SSS shall list the data that can vary according to operational needs and any site–dependant data, including the system database.
<<<

[[/SECTION]]

[[SECTION]]
TITLE: Computer resource requirements (5.3.8.1)

[[SECTION]]
TITLE: Computer hardware resource requirements

[TEXT]
STATEMENT: >>>
a. The SSS shall list the requirements on the computer hardware to be used.
<<<

[[/SECTION]]

[[SECTION]]
TITLE: Computer hardware resource utilization requirements

[TEXT]
STATEMENT: >>>
a. The SSS shall list the requirements on the computer resource utilization (e.g. processor capacity and memory capacity) available for the software item (e.g. sizing and timing).
<<<

[[/SECTION]]

[[SECTION]]
TITLE: Computer software resource requirements

[TEXT]
STATEMENT: >>>
a. The SSS shall list requirements on the software items to be used by or incorporated into the system (or constituent software product) (e.g. a specific real time operating system)
<<<

[[/SECTION]]

[[/SECTION]]

[[SECTION]]
TITLE: Security requirements (5.2.2.1g.)

[TEXT]
STATEMENT: >>>
The SSS shall list the security requirements applicable to the system.
<<<

[[/SECTION]]

[[SECTION]]
TITLE: Safety requirements (5.2.4.8)

[TEXT]
STATEMENT: >>>
a. The SSS shall list the safety requirements applicable to the system.
<<<

[[/SECTION]]

[[SECTION]]
TITLE: Reliability and availability requirements (5.2.4.8)

[TEXT]
STATEMENT: >>>
The SSS shall list the reliability and availability requirements applicable to the system.
<<<

[[/SECTION]]

[[SECTION]]
TITLE: Quality requirements

[TEXT]
STATEMENT: >>>
a. The SSS shall list the quality requirements applicable to the software (e.g. usability, reusability (5.2.4.7), and portability), and the applicable software development standards (5.2.4.5)

   NOTE: When future reuse of developed software components is a requirement, the customer specifies the generic application domain of these components. This can, for example, include requirements on software architecture for given target computers and operating systems, the interfaces required for reuse and the level where reuse is required (e.g. function, sub–system, and code units).
<<<

[[/SECTION]]

[[SECTION]]
TITLE: Design requirements and constraints (5.2.4.5)

[TEXT]
STATEMENT: >>>
a. The SSS shall include the requirements which constraint the design and production of the system.

   NOTE: When the software is integrated into a system, the customer can check for applicability of some harmonization constraints such as: specification of the operating system to be used, specification of COTS to be used (e.g. database and HMI generator), and specification of the SDE to be used.

b. At least, the following type of requirements shall be considered:

   1. constraints on the software architecture,
   2. utilization of standards,
   3. utilization of existing components,
   4. utilization of customer furnished components or COTS components,

      NOTE 1: For instance, a database can be used to produce automatically configured software (e.g. generation of tables, constant data, initial values).

      NOTE 2: For instance, a database can be, according to ECSS‐E‐ST‐10 and ECSS‐E‐ST‐70, e.g. a mission–operations database, an operational database of ground elements, a space segment database or a spacecraft database.

   5. utilization of design standard,
   6. utilization of data standard,
   7. utilization of a specific programming language,
   8. utilization of specific naming convention,
   9. flexibility and expansion, and
   10. utilization of HMI standards.
<<<

[[/SECTION]]

[[SECTION]]
TITLE: Software operations requirements (5.2.2.1c.)

[TEXT]
STATEMENT: >>>
a. The SSS shall include the system requirements for the operation of the software.

   NOTE: The supplier’s response is provided in releasing the operational plan for execution as established in clause 5.9.
<<<

[[/SECTION]]

[[SECTION]]
TITLE: Software maintenance requirements (5.2.2.1d., e.)

[TEXT]
STATEMENT: >>>
a. The SSS shall include the system requirements for the maintenance of the software (including the system requirements for in flight modifications capabilities).

   NOTE 1: The supplier’s response is agreed with the customer in the system requirements review (SRR), intended to release the maintenance plan for execution as established in clause 5.10.

   NOTE 2: Due to the long lifetimes often encountered with flight software, special requirements also exist to ensure that the supporting tools (e.g. compilers, engineering tools and inflight modification tools) can support the in–orbit reprogramming during the specified lifetime.
<<<

[[/SECTION]]

[[SECTION]]
TITLE: System and software observability requirements (5.2.2.2)

[TEXT]
STATEMENT: >>>
a. The SSS shall include the system and software requirements for the observability of the system

   NOTE 1: Observability requirements can impair the performance requirements (e.g. computer throughput, bandwidth, and ground exploitation rate of telecommands). This has an impact when specifying the observability requirements (e.g. considering the need of oversampling).

   NOTE2: In case of ACG the capability of a code generator to automatically instrument the code ‐ and to remove such code parts ‐ to cover observability requirements is considered.
<<<

[[/SECTION]]

[[/SECTION]]

[[SECTION]]
TITLE: Verification, validation and system integration

[[SECTION]]
TITLE: Verification and validation process requirements (5.2.3.1)

[TEXT]
STATEMENT: >>>
a. The SSS shall include the requirements needed for planning and setting up the system verification and validation process related to software

   NOTE: Specific customer requirements (e.g. availability or usage of customer furnished equipment like ETM, EM, FM and related ground systems) are needed in order to plan and to set up the system level verification and validation processes related to software. Furthermore, it is important to define for each testing or mission phase, or mission increment as far as applicable, any usage of hardware/software simulators , as representative flight and ground environments, for system payloads’ and experiments’ (pre‐) integration testing, hardware/software compatibility as well for acceptance testing.
<<<

[[/SECTION]]

[[SECTION]]
TITLE: Validation approach (5.2.3.2)

[TEXT]
STATEMENT: >>>
a. The SSS shall include the requirements for the validation of the software against requirements baseline and technical specification, in particular mission representative data and scenarios, and operational procedures to be used.
<<<

[[/SECTION]]

[[SECTION]]
TITLE: Validation requirements (5.2.2.1b.)

[TEXT]
STATEMENT: >>>
a. The SSS shall describe the validation requirements specified to support the demonstration that software requirements are met.

b. For each of the identified requirements in 5.2.2.1b., a validation method shall be included.

c. If a given requirement need not to be taken into account for the software validation against the requirements baseline, then it should be clearly identified.

   NOTE: A matrix (requirements to validation method correlation table) can be used to state the validation methods applicable to each requirement. This information can be further split into an information for validation requirements and an information for acceptance requirements, depending upon the project needs.
<<<

[[/SECTION]]

[[SECTION]]
TITLE: Verification requirements (5.2.2.1b.)

[TEXT]
STATEMENT: >>>
a. The SSS shall include requirements for

1. the installation and acceptance of the software (5.2.3.3,)

2. the needed versions, their content and their medium (5.2.4.1,)

3. the needed supplier support for system integration (5.2.4.2)

4. the format and delivery medium of all exchanged data in the project, including the interface and the system database (5.2.4.9)
<<<

[[/SECTION]]

[[/SECTION]]

[[SECTION]]
TITLE: System models

[TEXT]
STATEMENT: >>>
a. The system models may be placed as appendix to the SSS if a specification language is used to support the system and software co‐ engineering processes in order to enable the generation of the software specification and architecture from the (formal) system specification

   NOTE: The system specification language intends to produce in particular the computational model, the data model, the functional model, the event model and the failure model. The models include at least the definition of the logical properties, the liveliness properties and the timeless properties. The models are exercised to verify the properties by schedulability analysis or model checking.
<<<

[[/SECTION]]
