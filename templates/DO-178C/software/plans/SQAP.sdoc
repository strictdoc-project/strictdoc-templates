[DOCUMENT]
TITLE: Software Quality Assurance Plan

[TEXT]
STATEMENT: >>>
Establishes methods used to satisfy software quality assurance process. It includes description of improvement, quality metrics
<<<

[[SECTION]]
TITLE: Environment

[[/SECTION]]

[[SECTION]]
TITLE: Authority

[[/SECTION]]

[[SECTION]]
TITLE: Activities

[[/SECTION]]

[[SECTION]]
TITLE: Transition criteria

[[/SECTION]]

[[SECTION]]
TITLE: Timing

[[/SECTION]]

[[SECTION]]
TITLE: Software quality assurance records

[[/SECTION]]

[[SECTION]]
TITLE: Supplier oversight

[[/SECTION]]
