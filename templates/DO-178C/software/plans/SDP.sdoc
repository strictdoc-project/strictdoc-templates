[DOCUMENT]
TITLE: Software Development Plan

[TEXT]
STATEMENT: >>>
Desribes the software development procedures, life cycle
<<<

[[SECTION]]
TITLE: Standards

[TEXT]
STATEMENT: >>>
Links to software requirements, design, coding standards.
Links to previously developed software or COTS software standards.
<<<

[[/SECTION]]

[[SECTION]]
TITLE: Software life cycle

[TEXT]
STATEMENT: >>>
Details the different processes and transition criteria to develop the software.
<<<

[[/SECTION]]

[[SECTION]]
TITLE: Software development environment

[[/SECTION]]
