[DOCUMENT]
TITLE: Plan for Software Aspect Of Certification

[TEXT]
STATEMENT: >>>
This document links applicant to certification authorities
<<<

[[SECTION]]
TITLE: System overview

[TEXT]
STATEMENT: >>>
Description of the system functions, system design, allocation to hardware and software components, safety features
<<<

[[/SECTION]]

[[SECTION]]
TITLE: Software overview

[TEXT]
STATEMENT: >>>
Description of the software functions, safety, partitionning, redundancy, timing and scheduling, hardware resource allocation and sharing...
<<<

[[/SECTION]]

[[SECTION]]
TITLE: Certification consideration

[TEXT]
STATEMENT: >>>
Expose the software design assurance level, software contribution to system failure conditions
<<<

[[/SECTION]]

[[SECTION]]
TITLE: Software lifecyle

[[/SECTION]]

[[SECTION]]
TITLE: Software lifecycle data

[[/SECTION]]

[[SECTION]]
TITLE: Schedule

[[/SECTION]]

[[SECTION]]
TITLE: Additional consideration

[[/SECTION]]

[[SECTION]]
TITLE: Supplier oversight

[[/SECTION]]
