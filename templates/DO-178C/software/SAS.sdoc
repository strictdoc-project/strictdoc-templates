[DOCUMENT]
TITLE: Software Accomplishment Summary

[TEXT]
STATEMENT: >>>
This is the primary item demonstrating compliance to Plan for Software Aspect of Certification.
<<<

[[SECTION]]
TITLE: System overview

[[/SECTION]]

[[SECTION]]
TITLE: Software overview

[[/SECTION]]

[[SECTION]]
TITLE: Certification considerations

[[/SECTION]]

[[SECTION]]
TITLE: Software life cycle

[[/SECTION]]

[[SECTION]]
TITLE: Software life cycle data

[[/SECTION]]

[[SECTION]]
TITLE: Additional considerations

[[/SECTION]]

[[SECTION]]
TITLE: Supplier oversight

[[/SECTION]]

[[SECTION]]
TITLE: Software identification

[[/SECTION]]

[[SECTION]]
TITLE: Software characteristics

[[/SECTION]]

[[SECTION]]
TITLE: Change history

[[/SECTION]]

[[SECTION]]
TITLE: Software status

[[/SECTION]]

[[SECTION]]
TITLE: Compliance statement

[[/SECTION]]
