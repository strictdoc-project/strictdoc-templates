[DOCUMENT]
TITLE: Software Code Standard

[TEXT]
STATEMENT: >>>
Programming language, versions of language standard, cyber security rules, control flow authorized structure, memory management, exceptional and abnormal conditions management, algorithmic and logical complexity limitations ...
<<<
