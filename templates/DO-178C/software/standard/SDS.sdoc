[DOCUMENT]
TITLE: Software Design Standard

[TEXT]
STATEMENT: >>>
Defines design method and tools, architecture and design constraints, complexity limitations (maximum number of nested call, recursion, multi threading synchronization...).
<<<
