[DOCUMENT]
TITLE: Software Verification Results

[TEXT]
STATEMENT: >>>
Software verification results are produced by the software verification process. For each identified review, analysis, test procedure, it shall indicate the pass/fail status. Any discrepancies should be recorded and tracked via problem reporting.
<<<
