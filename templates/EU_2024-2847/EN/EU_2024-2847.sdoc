[DOCUMENT]
MID: bb22d107c8a2498ebc193dcd5bd2ce95
TITLE: EU Regulation 2024/2847 EN (20.11.2024)
PREFIX: EU_2024-2847-
OPTIONS:
  ENABLE_MID: True

[GRAMMAR]
IMPORT_FROM_FILE: grammar.sgra

[TEXT]
MID: 61fa91a98e1c46fa962def09fa0ca33e
STATEMENT: >>>
Reformatted from: https://eur-lex.europa.eu/legal-content/EN/TXT/PDF/?uri=OJ:L_202402847

This document is informally known as the EU Cyber Resilience Act.
<<<

[TEXT]
MID: 9d027a79fd814e38bab52daf886ded9d
STATEMENT: >>>
2024/2847     20.11.2024

REGULATION (EU) 2024/2847 OF THE EUROPEAN PARLIAMENT AND OF THE COUNCIL

of 23 October 2024

on horizontal cybersecurity requirements for products with digital elements and amending 

Regulations (EU) No 168/2013 and (EU) No 2019/1020 and Directive (EU) 2020/1828 (Cyber 
Resilience Act)

(Text with EEA relevance)
<<<

[[SECTION]]
MID: 84d99fd88c50402488960c6469d51b25
UID: EU-CRA-2024-CHAPTER-I
TITLE: CHAPTER I - GENERAL PROVISIONS

[[/SECTION]]

[[SECTION]]
MID: 80dd918d28ed4a11bd5e46b329d03b77
UID: EU-CRA-2024-CHAPTER-II
TITLE: CHAPTER II - OBLIGATIONS OF ECONOMIC OPERATORS AND PROVISIONS IN RELATION TO FREE AND OPEN-SOURCE SOFTWARE

[[/SECTION]]

[[SECTION]]
MID: 44b2f53d07a945d59eff0f121f7df161
UID: EU-CRA-2024-CHAPTER-III
TITLE: CHAPTER III - CONFORMITY OF THE PRODUCT WITH DIGITAL ELEMENTS

[[/SECTION]]

[[SECTION]]
MID: 8e93076e8cf345d081077117bdf92db7
UID: EU-CRA-2024-CHAPTER-IV
TITLE: CHAPTER IV - NOTIFICATION OF CONFORMITY ASSESSMENT BODIES

[[/SECTION]]

[[SECTION]]
MID: f563cc4d3c5e4f4d95cc03b4511eef07
UID: EU-CRA-2024-CHAPTER-V
TITLE: CHAPTER V - MARKET SURVEILLANCE AND ENFORCEMENT

[[/SECTION]]

[[SECTION]]
MID: 6618d90412814ccca5dc9e0aa221ad80
UID: EU-CRA-2024-CHAPTER-VI
TITLE: CHAPTER VI - DELEGATED POWERS AND COMMITTEE PROCEDURE

[[/SECTION]]

[[SECTION]]
MID: 2db5033a006b447480e14b4de617ad0d
UID: EU-CRA-2024-CHAPTER-VII
TITLE: CHAPTER VII - CONFIDENTIALITY AND PENALTIES

[[/SECTION]]

[[SECTION]]
MID: 2c93dadd9cbb4b919035c36689f78674
UID: EU-CRA-2024-CHAPTER-VIII
TITLE: CHAPTER VIII - TRANSITIONAL AND FINAL PROVISIONS

[[/SECTION]]

[DOCUMENT_FROM_FILE]
FILE: EU_2024-2847-ANNEX-I.sdoc

[[SECTION]]
MID: 54ddcb39597a444eaf949775bda360ae
UID: EU-CRA-2024-ANNEX-II
TITLE: ANNEX II - INFORMATION AND INSTRUCTIONS TO THE USER

[[/SECTION]]

[DOCUMENT_FROM_FILE]
FILE: EU_2024-2847-ANNEX-III.sdoc

[DOCUMENT_FROM_FILE]
FILE: EU_2024-2847-ANNEX-IV.sdoc

[DOCUMENT_FROM_FILE]
FILE: EU_2024-2847-ANNEX-V.sdoc

[DOCUMENT_FROM_FILE]
FILE: EU_2024-2847-ANNEX-VI.sdoc

[DOCUMENT_FROM_FILE]
FILE: EU_2024-2847-ANNEX-VII.sdoc

[DOCUMENT_FROM_FILE]
FILE: EU_2024-2847-ANNEX-VIII.sdoc
