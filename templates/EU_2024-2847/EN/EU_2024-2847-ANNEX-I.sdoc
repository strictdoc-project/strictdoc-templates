[DOCUMENT]
MID: 6c4df650457840bebd8137d09fc151c9
TITLE: ANNEX I - ESSENTIAL CYBERSECURITY REQUIREMENTS
OPTIONS:
  ENABLE_MID: True

[GRAMMAR]
IMPORT_FROM_FILE: grammar.sgra

[[SECTION]]
MID: c6521ae2e0b54dd5a713427fe53fec27
UID: EU-CRA-2024-ANNEX-I-Part-I
TITLE: Part I Cybersecurity requirements relating to the properties of products with digital elements

[REQUIREMENT]
MID: 4e6b0643b7b946319e08297299e05913
UID: EU-CRA-2024-ANNEX-I-Part-I-1
TITLE: ANNEX I Part I(1)
STATEMENT: >>>
Products with digital elements shall be designed, developed and produced in such a way that they ensure an appropriate 
level of cybersecurity based on the risks.
<<<

[REQUIREMENT]
MID: a689174dcf6040b696d6044a06c721f8
UID: EU-CRA-2024-ANNEX-I-Part-I-2a
TITLE: ANNEX I Part I(2)a
STATEMENT: >>>
[On the basis of the cybersecurity risk assessment referred to in Article 13(2) and where applicable, 
products with digital elements shall]

be made available on the market without known exploitable vulnerabilities;
<<<

[REQUIREMENT]
MID: edbdfc349f504c5eb3eca036cfed3f97
UID: EU-CRA-2024-ANNEX-I-Part-I-2b
TITLE: ANNEX I Part I(2)b
STATEMENT: >>>
[On the basis of the cybersecurity risk assessment referred to in Article 13(2) and where applicable, 
products with digital elements shall]

be made available on the market with a secure by default configuration, 

unless otherwise agreed between manufacturer and business user in relation to a tailor-made product with digital elements, 

including the possibility to reset the product to its original state;
<<<

[REQUIREMENT]
MID: 8065bb35c06e436989c8057e0fae16ee
UID: EU-CRA-2024-ANNEX-I-Part-I-2c
TITLE: ANNEX I Part I(2)c
STATEMENT: >>>
[On the basis of the cybersecurity risk assessment referred to in Article 13(2) and where applicable, 
products with digital elements shall]

ensure that vulnerabilities can be addressed through security updates, 
including, where applicable, 

through automatic security updates that are installed within an appropriate timeframe enabled as a default setting, 

with a clear and easy-to-use opt-out mechanism, 

through the notification of available updates to users, 

and the option to temporarily postpone them;
<<<

[REQUIREMENT]
MID: bb838f10573842ada6031501e9ff86e1
UID: EU-CRA-2024-ANNEX-I-Part-I-2d
TITLE: ANNEX I Part I(2)d
STATEMENT: >>>
[On the basis of the cybersecurity risk assessment referred to in Article 13(2) and where applicable, 
products with digital elements shall]

ensure protection from unauthorised access by appropriate control mechanisms, 

including but not limited to 

authentication, 

identity or access management systems, 

and report on possible unauthorised access;
<<<

[REQUIREMENT]
MID: 20f85646459f46db8dfa9b51fdefc4d8
UID: EU-CRA-2024-ANNEX-I-Part-I-2e
TITLE: ANNEX I Part I(2)e
STATEMENT: >>>
[On the basis of the cybersecurity risk assessment referred to in Article 13(2) and where applicable, 
products with digital elements shall]

protect the confidentiality of stored, transmitted or otherwise processed data, personal or other, 

such as by encrypting relevant data at rest or in transit by state of the art mechanisms, 

and by using other technical means;
<<<

[REQUIREMENT]
MID: 8942852aa75744408288e8802b329186
UID: EU-CRA-2024-ANNEX-I-Part-I-2f
TITLE: ANNEX I Part I(2)f
STATEMENT: >>>
[On the basis of the cybersecurity risk assessment referred to in Article 13(2) and where applicable, 
products with digital elements shall]

protect the integrity of stored, transmitted or otherwise processed 

data, personal or other, 

commands, 

programs 

and configuration 

against any manipulation or modification not authorised by the user, 

and report on corruptions;
<<<

[REQUIREMENT]
MID: 8171cc6faf3b4d368f8744c49d72534a
UID: EU-CRA-2024-ANNEX-I-Part-I-2g
TITLE: ANNEX I Part I(2)g
STATEMENT: >>>
[On the basis of the cybersecurity risk assessment referred to in Article 13(2) and where applicable, 
products with digital elements shall]

process only data, personal or other, that are 

adequate, 

relevant and 

limited 

to what is necessary in relation to the intended purpose of the product with digital elements (data minimisation);
<<<

[REQUIREMENT]
MID: addcd283a0d24bd1938c526296859faa
UID: EU-CRA-2024-ANNEX-I-Part-I-2h
TITLE: ANNEX I Part I(2)h
STATEMENT: >>>
[On the basis of the cybersecurity risk assessment referred to in Article 13(2) and where applicable, 
products with digital elements shall]

protect the availability of essential and basic functions, also after an incident, 

including through 

resilience and 

mitigation measures 

against denial-of-service attacks;
<<<

[REQUIREMENT]
MID: b4fa34cbcbc44ff5a67c3c2295dede34
UID: EU-CRA-2024-ANNEX-I-Part-I-2i
TITLE: ANNEX I Part I(2)i
STATEMENT: >>>
[On the basis of the cybersecurity risk assessment referred to in Article 13(2) and where applicable, 
products with digital elements shall]

minimise the negative impact by the products themselves or connected devices on 

the availability of services provided by other devices or networks;
<<<

[REQUIREMENT]
MID: 8efb6f8084cb4cff8f2a9fbc2818f08f
UID: EU-CRA-2024-ANNEX-I-Part-I-2j
TITLE: ANNEX I Part I(2)j
STATEMENT: >>>
[On the basis of the cybersecurity risk assessment referred to in Article 13(2) and where applicable, 
products with digital elements shall]

be designed, developed and produced to 

limit attack surfaces, including external interfaces;
<<<

[REQUIREMENT]
MID: 1440f6143dac447bb5c47e21fcb7a46f
UID: EU-CRA-2024-ANNEX-I-Part-I-2k
TITLE: ANNEX I Part I(2)k
STATEMENT: >>>
[On the basis of the cybersecurity risk assessment referred to in Article 13(2) and where applicable, 
products with digital elements shall]

be designed, developed and produced to 

reduce the impact of an incident using appropriate exploitation mitigation mechanisms and techniques;
<<<

[REQUIREMENT]
MID: daf20cb4d39b45d1a0e9fc533c6d61c0
UID: EU-CRA-2024-ANNEX-I-Part-I-2l
TITLE: ANNEX I Part I(2)l
STATEMENT: >>>
[On the basis of the cybersecurity risk assessment referred to in Article 13(2) and where applicable, 
products with digital elements shall]

provide security related information by 

recording and monitoring relevant internal activity, 

including the access to or modification of data, services or functions, 

with an opt-out mechanism for the user;
<<<

[REQUIREMENT]
MID: 7393e04768034756a70a3441741d5f50
UID: EU-CRA-2024-ANNEX-I-Part-I-2m
TITLE: ANNEX I Part I(2)m
STATEMENT: >>>
[On the basis of the cybersecurity risk assessment referred to in Article 13(2) and where applicable, 
products with digital elements shall]

provide the possibility for users to securely and easily remove on a permanent basis all data and settings 

and, where such data can be transferred to other products or systems, ensure that this is done in a secure manner.
<<<

[[/SECTION]]

[[SECTION]]
MID: 10f84172389944eca5c00371d8939357
UID: EU-CRA-2024-ANNEX-I-Part-II
TITLE: Part II Vulnerability handling requirements

[REQUIREMENT]
MID: 32805b3d43504fce99ad4102259bd228
UID: EU-CRA-2024-ANNEX-I-Part-II-1
TITLE: ANNEX I Part II(1)
STATEMENT: >>>
[Manufacturers of products with digital elements shall]

identify and document vulnerabilities and components contained in products with digital elements, 

including by drawing up a software bill of materials in a commonly used and machine-readable format 

covering at the very least the top-level dependencies of the products;
<<<

[REQUIREMENT]
MID: 26953cea7dd0401a81caa80becc1c873
UID: EU-CRA-2024-ANNEX-I-Part-II-2
TITLE: ANNEX I Part II(2)
STATEMENT: >>>
[Manufacturers of products with digital elements shall]

in relation to the risks posed to products with digital elements, 

address and remediate vulnerabilities without delay, 

including by providing security updates; 

where technically feasible, new security updates shall be provided separately from functionality updates;
<<<

[REQUIREMENT]
MID: 9defca9b421040c58f7e0557fb3d2d9d
UID: EU-CRA-2024-ANNEX-I-Part-II-3
TITLE: ANNEX I Part II(3)
STATEMENT: >>>
[Manufacturers of products with digital elements shall]

apply effective and regular tests and reviews of the security of the product with digital elements;
<<<

[REQUIREMENT]
MID: 43b9589a2257483b83aecfe18aa01688
UID: EU-CRA-2024-ANNEX-I-Part-II-4
TITLE: ANNEX I Part II(4)
STATEMENT: >>>
[Manufacturers of products with digital elements shall]

once a security update has been made available, 

share and publicly disclose information about fixed vulnerabilities, including a

description of the vulnerabilities, 

information allowing users to identify the product with digital elements affected, 

the impacts of the vulnerabilities, 

their severity and 

clear and accessible information helping users to remediate the vulnerabilities; 

in duly justified cases, 
where manufacturers consider the security risks of publication to outweigh the security benefits, 
they may delay making public information regarding a fixed vulnerability until after users have 
been given the possibility to apply the relevant patch;
<<<

[REQUIREMENT]
MID: f03f4f5818564373a3fd10be448ef8ad
UID: EU-CRA-2024-ANNEX-I-Part-II-5
TITLE: ANNEX I Part II(5)
STATEMENT: >>>
[Manufacturers of products with digital elements shall]

put in place and enforce a policy on coordinated vulnerability disclosure;
<<<

[REQUIREMENT]
MID: 4bf56ac58163451c829646ef8ef8f1cc
UID: EU-CRA-2024-ANNEX-I-Part-II-6
TITLE: ANNEX I Part II(6)
STATEMENT: >>>
[Manufacturers of products with digital elements shall]

take measures to facilitate the sharing of information about potential vulnerabilities 

in their product with digital elements as well as 

in third-party components contained in that product, 

including by providing a contact address for the reporting of the vulnerabilities discovered in the product with digital elements;
<<<

[REQUIREMENT]
MID: 3e9839903e9248119e07cfb72a51863d
UID: EU-CRA-2024-ANNEX-I-Part-II-7
TITLE: ANNEX I Part II(7)
STATEMENT: >>>
[Manufacturers of products with digital elements shall]

provide for mechanisms to securely distribute updates for products with digital elements 

to ensure that vulnerabilities are fixed or mitigated 

in a timely manner and, where applicable for security updates, in an automatic manner;
<<<

[REQUIREMENT]
MID: 61026619e8af4f799a713b22a2c44b05
UID: EU-CRA-2024-ANNEX-I-Part-II-8
TITLE: ANNEX I Part II(8)
STATEMENT: >>>
[Manufacturers of products with digital elements shall]

ensure that, where security updates are available to address identified security issues, 
they are disseminated without delay and, 

unless otherwise agreed between a manufacturer and a business user in relation to a tailor-made product with digital elements, 

free of charge, 

accompanied by advisory messages providing users with the relevant information, 

including on potential action to be taken.
<<<

[[/SECTION]]
