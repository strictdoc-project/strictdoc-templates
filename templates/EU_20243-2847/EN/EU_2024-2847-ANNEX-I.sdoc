[DOCUMENT]
TITLE: ANNEX I - ESSENTIAL CYBERSECURITY REQUIREMENTS

[[SECTION]]
TITLE: Part I Cybersecurity requirements relating to the properties of products with digital elements

[REQUIREMENT]
TITLE: ANNEX I Part I(1)
STATEMENT: >>>
Products with digital elements shall be designed, developed and produced in such a way that they ensure an appropriate 
level of cybersecurity based on the risks.
<<<

[REQUIREMENT]
TITLE: ANNEX I Part I(2)a
STATEMENT: >>>
[On the basis of the cybersecurity risk assessment referred to in Article 13(2) and where applicable, 
products with digital elements shall]

be made available on the market without known exploitable vulnerabilities;
<<<

[REQUIREMENT]
TITLE: ANNEX I Part I(2)b
STATEMENT: >>>
[On the basis of the cybersecurity risk assessment referred to in Article 13(2) and where applicable, 
products with digital elements shall]

be made available on the market with a secure by default configuration, 

unless otherwise agreed between manufacturer and business user in relation to a tailor-made product with digital elements, 

including the possibility to reset the product to its original state;
<<<

[REQUIREMENT]
TITLE: ANNEX I Part I(2)c
STATEMENT: >>>
[On the basis of the cybersecurity risk assessment referred to in Article 13(2) and where applicable, 
products with digital elements shall]

ensure that vulnerabilities can be addressed through security updates, 
including, where applicable, 

through automatic security updates that are installed within an appropriate timeframe enabled as a default setting, 

with a clear and easy-to-use opt-out mechanism, 

through the notification of available updates to users, 

and the option to temporarily postpone them;
<<<

[REQUIREMENT]
TITLE: ANNEX I Part I(2)d
STATEMENT: >>>
[On the basis of the cybersecurity risk assessment referred to in Article 13(2) and where applicable, 
products with digital elements shall]

ensure protection from unauthorised access by appropriate control mechanisms, 

including but not limited to 

authentication, 

identity or access management systems, 

and report on possible unauthorised access;
<<<

[REQUIREMENT]
TITLE: ANNEX I Part I(2)e
STATEMENT: >>>
[On the basis of the cybersecurity risk assessment referred to in Article 13(2) and where applicable, 
products with digital elements shall]

protect the confidentiality of stored, transmitted or otherwise processed data, personal or other, 

such as by encrypting relevant data at rest or in transit by state of the art mechanisms, 

and by using other technical means;
<<<

[REQUIREMENT]
TITLE: ANNEX I Part I(2)f
STATEMENT: >>>
[On the basis of the cybersecurity risk assessment referred to in Article 13(2) and where applicable, 
products with digital elements shall]

protect the integrity of stored, transmitted or otherwise processed 

data, personal or other, 

commands, 

programs 

and configuration 

against any manipulation or modification not authorised by the user, 

and report on corruptions;
<<<

[REQUIREMENT]
TITLE: ANNEX I Part I(2)g
STATEMENT: >>>
[On the basis of the cybersecurity risk assessment referred to in Article 13(2) and where applicable, 
products with digital elements shall]

process only data, personal or other, that are 

adequate, 

relevant and 

limited 

to what is necessary in relation to the intended purpose of the product with digital elements (data minimisation);
<<<

[REQUIREMENT]
TITLE: ANNEX I Part I(2)h
STATEMENT: >>>
[On the basis of the cybersecurity risk assessment referred to in Article 13(2) and where applicable, 
products with digital elements shall]

protect the availability of essential and basic functions, also after an incident, 

including through 

resilience and 

mitigation measures 

against denial-of-service attacks;
<<<

[REQUIREMENT]
TITLE: ANNEX I Part I(2)i
STATEMENT: >>>
[On the basis of the cybersecurity risk assessment referred to in Article 13(2) and where applicable, 
products with digital elements shall]

minimise the negative impact by the products themselves or connected devices on 

the availability of services provided by other devices or networks;
<<<

[REQUIREMENT]
TITLE: ANNEX I Part I(2)j
STATEMENT: >>>
[On the basis of the cybersecurity risk assessment referred to in Article 13(2) and where applicable, 
products with digital elements shall]

be designed, developed and produced to 

limit attack surfaces, including external interfaces;
<<<

[REQUIREMENT]
TITLE: ANNEX I Part I(2)k
STATEMENT: >>>
[On the basis of the cybersecurity risk assessment referred to in Article 13(2) and where applicable, 
products with digital elements shall]

be designed, developed and produced to 

reduce the impact of an incident using appropriate exploitation mitigation mechanisms and techniques;
<<<

[REQUIREMENT]
TITLE: ANNEX I Part I(2)l
STATEMENT: >>>
[On the basis of the cybersecurity risk assessment referred to in Article 13(2) and where applicable, 
products with digital elements shall]

provide security related information by 

recording and monitoring relevant internal activity, 

including the access to or modification of data, services or functions, 

with an opt-out mechanism for the user;
<<<

[REQUIREMENT]
TITLE: ANNEX I Part I(2)m
STATEMENT: >>>
[On the basis of the cybersecurity risk assessment referred to in Article 13(2) and where applicable, 
products with digital elements shall]

provide the possibility for users to securely and easily remove on a permanent basis all data and settings 

and, where such data can be transferred to other products or systems, ensure that this is done in a secure manner.
<<<

[[/SECTION]]

[[SECTION]]
TITLE: Part II Vulnerability handling requirements

[REQUIREMENT]
TITLE: ANNEX I Part II(1)
STATEMENT: >>>
[Manufacturers of products with digital elements shall]

identify and document vulnerabilities and components contained in products with digital elements, 

including by drawing up a software bill of materials in a commonly used and machine-readable format 

covering at the very least the top-level dependencies of the products;
<<<

[REQUIREMENT]
TITLE: ANNEX I Part II(2)
STATEMENT: >>>
[Manufacturers of products with digital elements shall]

in relation to the risks posed to products with digital elements, 

address and remediate vulnerabilities without delay, 

including by providing security updates; 

where technically feasible, new security updates shall be provided separately from functionality updates;
<<<

[REQUIREMENT]
TITLE: ANNEX I Part II(3)
STATEMENT: >>>
[Manufacturers of products with digital elements shall]

apply effective and regular tests and reviews of the security of the product with digital elements;
<<<

[REQUIREMENT]
TITLE: ANNEX I Part II(4)
STATEMENT: >>>
[Manufacturers of products with digital elements shall]

once a security update has been made available, 

share and publicly disclose information about fixed vulnerabilities, including a

description of the vulnerabilities, 

information allowing users to identify the product with digital elements affected, 

the impacts of the vulnerabilities, 

their severity and 

clear and accessible information helping users to remediate the vulnerabilities; 

in duly justified cases, 
where manufacturers consider the security risks of publication to outweigh the security benefits, 
they may delay making public information regarding a fixed vulnerability until after users have 
been given the possibility to apply the relevant patch;
<<<

[REQUIREMENT]
TITLE: ANNEX I Part II(5)
STATEMENT: >>>
[Manufacturers of products with digital elements shall]

put in place and enforce a policy on coordinated vulnerability disclosure;
<<<

[REQUIREMENT]
TITLE: ANNEX I Part II(6)
STATEMENT: >>>
[Manufacturers of products with digital elements shall]

take measures to facilitate the sharing of information about potential vulnerabilities 

in their product with digital elements as well as 

in third-party components contained in that product, 

including by providing a contact address for the reporting of the vulnerabilities discovered in the product with digital elements;
<<<

[REQUIREMENT]
TITLE: ANNEX I Part II(7)
STATEMENT: >>>
[Manufacturers of products with digital elements shall]

provide for mechanisms to securely distribute updates for products with digital elements 

to ensure that vulnerabilities are fixed or mitigated 

in a timely manner and, where applicable for security updates, in an automatic manner;
<<<

[REQUIREMENT]
TITLE: ANNEX I Part II(8)
STATEMENT: >>>
[Manufacturers of products with digital elements shall]

ensure that, where security updates are available to address identified security issues, 
they are disseminated without delay and, 

unless otherwise agreed between a manufacturer and a business user in relation to a tailor-made product with digital elements, 

free of charge, 

accompanied by advisory messages providing users with the relevant information, 

including on potential action to be taken.
<<<

[[/SECTION]]
