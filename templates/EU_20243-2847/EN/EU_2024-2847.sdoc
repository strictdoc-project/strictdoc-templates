[DOCUMENT]
TITLE: EU Regulation 2024/2847 EN (20.11.2024)
PREFIX: EU_2024-2847-

[TEXT]
STATEMENT: >>>
Reformatted from: https://eur-lex.europa.eu/legal-content/EN/TXT/PDF/?uri=OJ:L_202402847

This document is informally known as the EU Cyber Resilience Act.
<<<

[TEXT]
STATEMENT: >>>
2024/2847     20.11.2024

REGULATION (EU) 2024/2847 OF THE EUROPEAN PARLIAMENT AND OF THE COUNCIL

of 23 October 2024

on horizontal cybersecurity requirements for products with digital elements and amending 

Regulations (EU) No 168/2013 and (EU) No 2019/1020 and Directive (EU) 2020/1828 (Cyber 
Resilience Act)

(Text with EEA relevance)
<<<

[[SECTION]]
TITLE: CHAPTER I - GENERAL PROVISIONS

[[/SECTION]]

[[SECTION]]
TITLE: CHAPTER II - OBLIGATIONS OF ECONOMIC OPERATORS AND PROVISIONS IN RELATION TO FREE AND OPEN-SOURCE SOFTWARE

[[/SECTION]]

[[SECTION]]
TITLE: CHAPTER III - CONFORMITY OF THE PRODUCT WITH DIGITAL ELEMENTS

[[/SECTION]]

[[SECTION]]
TITLE: CHAPTER IV - NOTIFICATION OF CONFORMITY ASSESSMENT BODIES

[[/SECTION]]

[[SECTION]]
TITLE: CHAPTER V - MARKET SURVEILLANCE AND ENFORCEMENT

[[/SECTION]]

[[SECTION]]
TITLE: CHAPTER VI - DELEGATED POWERS AND COMMITTEE PROCEDURE

[[/SECTION]]

[[SECTION]]
TITLE: CHAPTER VII - CONFIDENTIALITY AND PENALTIES

[[/SECTION]]

[[SECTION]]
TITLE: CHAPTER VIII - TRANSITIONAL AND FINAL PROVISIONS

[[/SECTION]]

[DOCUMENT_FROM_FILE]
FILE: EU_2024-2847-ANNEX-I.sdoc

[[SECTION]]
TITLE: ANNEX II - INFORMATION AND INSTRUCTIONS TO THE USER

[[/SECTION]]

[DOCUMENT_FROM_FILE]
FILE: EU_2024-2847-ANNEX-III.sdoc

[DOCUMENT_FROM_FILE]
FILE: EU_2024-2847-ANNEX-IV.sdoc

[DOCUMENT_FROM_FILE]
FILE: EU_2024-2847-ANNEX-V.sdoc

[DOCUMENT_FROM_FILE]
FILE: EU_2024-2847-ANNEX-VI.sdoc

[DOCUMENT_FROM_FILE]
FILE: EU_2024-2847-ANNEX-VII.sdoc

[DOCUMENT_FROM_FILE]
FILE: EU_2024-2847-ANNEX-VIII.sdoc
